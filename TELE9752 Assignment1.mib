VendingMachine-MIB DEFINITIONS ::= BEGIN

IMPORTS
    OBJECT-TYPE, IpAddress        FROM SNMPv2-SMI
    DisplayString                 FROM SNMPv2-TC
    InetAddress                   FROM INET-ADDRESS-MIB;

VendingMachine     OBJECT IDENTIFIER ::= { enterprises 10 }

VendingMachine-MIB DEFINITIONS ::= BEGIN


-- 1. Machine Spec

machineSpecTable OBJECT-TYPE
    SYNTAX SEQUENCE OF MachineSpecTableEntry
    MAX-ACCESS read-write
    STATUS current
    DESCRIPTION 
        ""
    ::= { VendingMachine 1 }

    machineSpecTableEntry OBJECT-TYPE
        SYNTAX MachineSpecTableEntry
        MAX-ACCESS read-write
        STATUS current
        DESCRIPTION 
            ""
        ::= {machineSpecTable 1}

    MachineSpecTableEntry ::= SEQUENCE {
        machineModelName     DisplayString,
        machineModelNumber   INTEGER,
    }

    machineModelName OBJECT-TYPE
        SYNTAX DisplayString,
        MAX-ACCESS read-write
        STATUS current
        DESCRIPTION 
            ""
        ::= { machineSpecTableEntry 1}

    machineModelNumber OBJECT-TYPE
        SYNTAX INTEGER,
        MAX-ACCESS read-write
        STATUS current 
        DESCRIPTION 
            ""
        ::= { machineSpecTableEntry 2}


-- 2. Product Handbook

productHandbookTable OBJECT-TYPE
    SYNTAX SEQUENCE OF ProductHandbookTableEntry
    MAX-ACCESS read-write
    STATUS current
    DESCRIPTION 
        ""
    ::= { VendingMachine 2 }

    productHandbookTableEntry OBJECT-TYPE
        SYNTAX ProductHandbookTableEntry
        MAX-ACCESS read-write
        STATUS current
        DESCRIPTION 
            ""
        ::= {productHandbookTable 1}

    ProductHandbookTableEntry ::= SEQUENCE {
        hardwaresTextualName   DisplayString,
        softwareTextualName    DisplayString,
    }

    hardwaresTextualName OBJECT-TYPE
        SYNTAX DisplayString,
        MAX-ACCESS read-write
        STATUS current
        DESCRIPTION 
            ""
        ::= { productHandbookTableEntry 1}

    softwaresTextualName OBJECT-TYPE
        SYNTAX DisplayString,
        MAX-ACCESS read-write
        STATUS current 
        DESCRIPTION 
            ""
        ::= { productHandbookTableEntry 2}


-- 3. Physical Location

physicalLocationTable OBJECT-TYPE
    SYNTAX SEQUENCE OF PhysicalLocationTableEntry
    MAX-ACCESS read-write
    STATUS current
    DESCRIPTION 
        ""
    ::= { VendingMachine 3 }

    physicalLocationTableEntry OBJECT-TYPE
        SYNTAX PhysicalLocationTableEntry
        MAX-ACCESS read-write
        STATUS current
        DESCRIPTION 
            ""
        ::= {physicalLocationTable 1}

    PhysicalLocationTableEntry ::= SEQUENCE {
        macAddress      INTEGER,
        globalAddress   INTEGER,
    }

    macAddress OBJECT-TYPE
        SYNTAX INTEGER,
        MAX-ACCESS read-write
        STATUS current
        DESCRIPTION 
            ""
        ::= { physicalLocationTableEntry 1}

    globalAddress OBJECT-TYPE
        SYNTAX INTEGER,
        MAX-ACCESS read-write
        STATUS current 
        DESCRIPTION 
            ""
        ::= { physicalLocationTableEntry 2}


-- 4. Contact Person

personInfoTable OBJECT-TYPE
    SYNTAX SEQUENCE OF PersonInfoTableEntry
    MAX-ACCESS read-write
    STATUS current
    DESCRIPTION 
        "This table contains names of contact persons and corresponding phone numbers of each machine in case of problems."
    ::= {VendingMachine 4}
    
    --4.1 & 4.2 Contact Person Name & Phone Num
    personInfoTableEntry OBJECT-TYPE
        SYNTAX PersonInfoTableEntry
        MAX-ACCESS read-write
        STATUS current
        DESCRIPTION 
            "An entry in personInfoTable."
        ::= { personInfoTable 1 }
        
    -- Entry sequence
    PersonInfoTableEntry ::= SEQUENCE {
        contactName          DisplayString,
        phoneNumber          INTEGER,
    }
    
    contactName OBJECT-TYPE
        SYNTAX DisplayString
        MAX-ACCESS read-write
        STATUS current
        DESCRIPTION 
            "Name of the contact person."
        ::= { personInfoTableEntry 1 }
    
    phoneNumber OBJECT-TYPE
        SYNTAX INTEGER
        MAX-ACCESS read-write
        STATUS current
        DESCRIPTION 
            "Phone number of the contact person."
        ::= { personInfoTableEntry 2 }
    

-- 5. Last Visit Time

lastVisitTime OBJECT-TYPE
    SYNTAX DisplayString
    MAX-ACCESS read-write
    STATUS current
    DESCRIPTION 
        "This table contains the time since the machine last operated."
    ::= { VendingMachine 5 }


-- 6. Machine IP Address

ipAdEntAddr OBJECT-TYPE
    SYNTAX IpAddress
    MAX-ACCESS read-only
    STATUS current
    DESCRIPTION 
        "This table contains the IP Address of each machine"
    ::= { VendingMachine 6}


-- 7. Product Information

productInfoTable OBJECT-TYPE
    SYNTAX SEQUENCE OF ProductInfoTableEntry
    MAX-ACCESS read-write
    STATUS current
    DESCRIPTION 
        "This table stores all the information of the product in the vending machine.
        Each of the product is labeled with their name and cost, and their location and current selling record."
    ::= { VendingMachine 7 }

    -- 7.1 Instance of the ProductInfoTableEntry
    productInfoTableEntry OBJECT-TYPE
        SYNTAX ProductInfoTableEntry
        MAX-ACCESS read-write
        STATUS current
        DESCRIPTION 
            "An entry in the productInfoTable."
        ::= { productInfoTable 1 }

    -- Entry sequence
    ProductInfoTableEntry ::= SEQUENCE {
        shelfLabel          DisplayString,
        compartmentNumber   INTEGER,
        productName         INTEGER,
        productCost         DisplayString,
        numberDispensed     INTEGER,
        numberInStock       INTEGER,
    }

    shelfLabel OBJECT-TYPE
        SYNTAX DisplayString
        MAX-ACCESS read-write
        STATUS current
        DESCRIPTION 
            "This is the shlef label of the product. (A, B, C...)"
        ::= { productInfoTableEntry 1 }
    
    compartmentNumber OBJECT-TYPE
        SYNTAX INTEGER
        MAX-ACCESS read-write
        STATUS current
        DESCRIPTION 
            "This is the compartment number of the product. (1, 2, 3...)"
        ::= { productInfoTableEntry 2 }
    
    productName OBJECT-TYPE
        SYNTAX INTEGER
        MAX-ACCESS read-write
        STATUS current
        DESCRIPTION 
            "This is the name of the product. (coke, fanta...)"
        ::= { productInfoTableEntry 3 }
    
    productCost OBJECT-TYPE
        SYNTAX DisplayString
        MAX-ACCESS read-write
        STATUS current
        DESCRIPTION 
            "This is the cost (in cents) of the product."
        ::= { productInfoTableEntry 4 }
    
    numberDispensed OBJECT-TYPE
        SYNTAX INTEGER
        MAX-ACCESS read-write
        STATUS current
        DESCRIPTION 
            "This is the number of products dispensed by the vending machine since the last switch on."
        ::= { productInfoTableEntry 5 }
    
    numberInStock OBJECT-TYPE
        SYNTAX INTEGER
        MAX-ACCESS read-write
        STATUS current
        DESCRIPTION 
            "This is the current product's number in stock."
        ::= { productInfoTableEntry 6 }


-- 8. Current Balance

currentBalanceTable OBJECT-TYPE
    SYNTAX SEQUENCE OF CurrentBalanceTableEntry
    MAX-ACCESS read-write
    STATUS current
    DESCRIPTION 
        "This table stores all the balance information of the vending machine. It indicates all types of denomincation
        and the number left in the machine for further use."
    ::= { VendingMachine 8 }

    currentBalanceTableEntry OBJECT-TYPE
        SYNTAX CurrentBalanceTableEntry
        MAX-ACCESS read-write
        STATUS current
        DESCRIPTION 
            "An entry in the currentBalanceTable."
        ::= { currentBalanceTable 1 }
    
    CurrentBalanceTableEntry ::= SEQUENCE {
        denomination INTEGER,
        totalNumber  INTEGER,
    }

    denomination OBJECT-TYPE
        SYNTAX INTEGER,
        MAX-ACCESS read-write
        STATUS current
        DESCRIPTION 
            "This is the coin type which indexed in cents."
        ::= { currentBalanceTableEntry 1 }
    
    totalNumber OBJECT-TYPE
        SYNTAX INTEGER,
        MAX-ACCESS read-write
        STATUS current
        DESCRIPTION 
            "This is the total number of coins left inside the machine for the particular denomination."
        ::= { currentBalanceTableEntry 2 }


-- 9. Deposited value

depositedValue OBJECT-TYPE
    SYNTAX INTEGER
    MAX-ACCESS read-write
    STATUS current
    DESCRIPTION 
            "This is the amount of money depoisted for a certain product which hasn't been dispensed."
    ::= { VendingMachine 9 }

END
